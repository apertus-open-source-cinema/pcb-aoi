#usage "<b>Export Pad Coordinates to Top/Bottom CSVs</b>\n"
       "<p>This ULP exports the X and Y coordinates (in mm) for top and bottom "
       "component designator and pad name for all pads/SMDs on the board.</p>"
       "<author>Author: Gemini</author>"

string outputFileName;

// Ensure the script is being run from the Board Editor
if (!board) {
    dlgMessageBox("!Error: Please run this ULP from the PCB Board Editor.");
    exit(1);
}

board(B) {
    // Generate a default output filename based on the current board name
    outputFileName = filesetext(B.name, "_pads.csv");

    // Prompt the user to choose a save location
    outputFileName = dlgFileSave("Save Pad Coordinates (Base Name)", outputFileName, "CSV Files (*.csv)");

    if (outputFileName != "") {
        string base = filesetext(outputFileName, "");
        string topPath = base + "_top.csv";
        string botPath = base + "_bot.csv";

        // Export Top Side
        output(topPath) {
            printf("Designator,Pad,X (mm),Y (mm)\n");
            B.elements(E) {
                E.package.contacts(C) {
                    // Layer 1 is Top. C.pad is true for through-hole.
                    if (C.pad || (C.smd && C.smd.layer == 1)) {
                        printf("%s,%s,%.4f,%.4f\n", E.name, C.name, u2mm(C.x), u2mm(C.y));
                    }
                }
            }
        }

        // Export Bottom Side
        output(botPath) {
            printf("Designator,Pad,X (mm),Y (mm)\n");
            B.elements(E) {
                E.package.contacts(C) {
                    // Layer 16 is Bottom. C.pad is true for through-hole.
                    if (C.pad || (C.smd && C.smd.layer == 16)) {
                        printf("%s,%s,%.4f,%.4f\n", E.name, C.name, u2mm(C.x), u2mm(C.y));
                    }
                }
            }
        }

        // Notify the user of success
        dlgMessageBox("Export completed successfully!\n\nFiles saved:\n" + topPath + "\n" + botPath);
    } else {
        // User cancelled the file dialog
        exit(0);
    }
}
